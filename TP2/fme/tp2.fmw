FME workspace tp2.fmw

Parameters:
- SourceDataset_GEOJSON_11 = https://github.com/ibrahimakhalil2701/geo7630h25/blob/308a3395ad70118473f1ad883c7be8553df83dfd/TP2/data/input/Donnee_tp2/limites-administratives-agglomeration-nad83.geojson   # Source GeoJSON File or URL
- SourceDataset_GEOJSON = https://github.com/ibrahimakhalil2701/geo7630h25/blob/main/TP2/data/input/Donnee_tp2/limites-administratives-agglomeration-nad83.geojson   # Source GeoJSON File or URL
- SourceDataset_GEOJSON_10 = https://montreal-prod.storage.googleapis.com/resources/6b313375-d9bc-4dc3-af8e-ceae3762ae6e/limites-administratives-agglomeration-nad83.geojson?X-Goog-Algorithm=GOOG4-RSA-SHA256&X-Goog-Credential=test-datapusher-delete%40amplus-data.iam.gserviceaccount.com%2F20250308%2Fauto%2Fstorage%2Fgoog4_request&X-Goog-Date=20250308T032206Z&X-Goog-Expires=604800&X-Goog-SignedHeaders=host&x-goog-signature=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   # Source GeoJSON File or URL
- SourceDataset_CSV2 = https://drive.usercontent.google.com/download?id=1CqNQqT8m9W0mUNAh6-9lCCttNgNKqVxc&export=download&authuser=1&confirm=t&uuid=55535f95-b2fd-4111-964c-30ff16829d77&at=AEz70l408cIiC51lgo1jFv3d_nct:1741664101192   # Source CSV (Comma Separated Value) File(s)
- SourceDataset_OGCGEOPACKAGE = https://drive.usercontent.google.com/download?id=1q4cLar7ljuaHBEWwUSJtY7XX_PUAu0fb&export=download&authuser=1&confirm=t&uuid=6b1b0cfd-2292-4d54-a9f9-e91b559ac46f&at=AEz70l7Ld5JxhdPzKl3qcBgiLURI:1741664219231   # GeoPackage File
- DestDataset_POSTGIS = geo7630   # Connection

Readers:
- GEOJSON_1: GEOJSON from $(SourceDataset_GEOJSON)
- GEOJSON_4: GEOJSON from $(SourceDataset_GEOJSON_11)
- GEOJSON_6: GEOJSON from $(SourceDataset_GEOJSON_10)
- CSV2_1: CSV2 from $(SourceDataset_CSV2)
- OGCGEOPACKAGE_1: OGCGEOPACKAGE from $(SourceDataset_OGCGEOPACKAGE)

Writers:
- POSTGIS_1: POSTGIS to $(DestDataset_POSTGIS)

Table1 (writer POSTGIS_1)
    attributes: codeid int8, nom varchar, dauid text, fid int8,PrimaryKey, revenu_median int8, nombre_menages_faible_revenu int8, pourcentage_population_active_15_64_ans int8, nombre_pop_total int8, nombre_pop_total_par_arrondissement float8

Bookmark: Arrondissement de montréal
limites-administratives-agglomeration-nad83 (reader GEOJSON_6)
    attributes: CODEID int, NOM string, NOM_OFFICIEL string, CODEMAMH string, CODE_3C string, NUM int, ABREV string, TYPE string, COMMENT string, DATEMODIF string
    -> Reprojector
Reprojector
    DEST = EPSG:32198
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeManager_2
AttributeManager_2
    ATTR_TABLE:
      REMOVE NOM_OFFICIEL (buffer)
      REMOVE CODEMAMH (buffer)
      REMOVE CODE_3C (buffer)
      REMOVE NUM (int64)
      REMOVE ABREV (buffer)
      REMOVE TYPE (buffer)
      REMOVE COMMENT (buffer)
      REMOVE DATEMODIF (buffer)
    USER_EXPOSED_ATTRIBUTES = Nombre_mÃ©nages_faible_revenu
    -> SpatialFilter [Filter]

Bookmark: Données de recensement stat can
Note: Couche des aires de division stat can
dcoup (reader OGCGEOPACKAGE_1)
    attributes: DAUID text, fid int,PrimaryKey
    -> Reprojector_2
Reprojector_2
    DEST = EPSG:32198
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> FeatureJoiner [LEFT]
CSV (reader CSV2_1)
    attributes: DAUID uint32, revenu_median uint32, Nombre_mÃ©nages_faible_revenu uint32, Pourcentage_population_active_15_64_ans uint32, nombre_pop_total uint32
    -> FeatureJoiner [RIGHT]
FeatureJoiner
    ATTR_CONFLICT_RES_LOOKUP = USE_LEFT
    GEOMETRY_HANDLING_LOOKUP = USE_LEFT
    JOIN_KEYS = DAUID DAUID AUTO
    JOIN_MODE = Inner
    ATTR_CONFLICT_RES = Prefer Left
    GEOMETRY_HANDLING = Prefer Left
    JOINED -> AttributeManager
    <REJECTED> -> Logger
AttributeManager
    ATTR_TABLE = RENAME_SET_VALUE Nombre_mÃ©nages_faible_revenu > Nombre_menages_faible_revenu (uint32)
    -> NullAttributeMapper
NullAttributeMapper
    ATTRCHOICE_ACTION = SELECTED
    ATTRLIST = Nombre_menages_faible_revenu nombre_pop_total Pourcentage_population_active_15_64_ans revenu_median
    NEW_VALUE = 0
    NULL_TREATMENT_LU = SETVALUE
    SOURCE_ATTR_VAL_LU = SETNULL
    ATTRCHOICE = Selected Attributes
    NULL_TREATMENT = New Value
    SOURCE_ATTR_VAL = Null
    -> SpatialFilter [Candidate]
Logger
    LOG_FEATURE = LOG_ONLY
    MAXCOORDS = 20
    MAXFEATS = 20
    MESSAGE = Feature is:
    SEVERITY = INFO

Bookmark: Joniture entre les air de division et les arrondissement
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
    <REJECTED> -> Logger_2
Logger_2
    LOG_FEATURE = LOG_ONLY
    MAXCOORDS = 20
    MAXFEATS = 20
    MESSAGE = Feature is:
    SEVERITY = INFO

Bookmark: calculer la densité de population par arrondissement
StatisticsCalculator
    ATTR_ACCUM_MODE = None
    CALCULATION_MODE = NUMERIC
    FEAT_STATS = nombre_pop_total,NUMERIC_MODE,,,,SUM,,,,,,,,,
    GROUP_BY = CODEID
    COMPLETE -> AttributeManager_3
AttributeManager_3
    ATTR_TABLE:
      REMOVE _predicate (buffer)
      RENAME_SET_VALUE nombre_pop_total.sum > nombre_pop_total_par_arrondissement (real64)
    -> Table1 (writer POSTGIS_1)
